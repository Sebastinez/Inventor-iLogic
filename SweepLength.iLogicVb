'Set a reference to the strings

Dim propertyName7 As String = InputBox("Enter Sweep Name", "Calculate Sweep Length", "Fill in sweep name (case sensitive) see in feature tree")

propertyName8 = " mm"


 'Set a reference to the active part document
    Dim oDoc As PartDocument
    oDoc = ThisApplication.ActiveDocument
    
    Dim oDef As PartComponentDefinition
    oDef = oDoc.ComponentDefinition

    Dim opath As Path
    opath = oDef.Features.SweepFeatures.Item(propertyName7).Path
	
    
    Dim TotalLength As Double
    TotalLength = 0
    
    Dim oCurve As Object
    Dim i As Integer

    For i = 1 To opath.Count
        oCurve = opath.Item(i).Curve
        
        Dim oCurveEval As CurveEvaluator
        oCurveEval = oCurve.Evaluator
        
        Dim MinParam As Double
        Dim MaxParam As Double
        Dim length As Double
        
        Call oCurveEval.GetParamExtents(MinParam, MaxParam)
        Call oCurveEval.GetLengthAtParam(MinParam, MaxParam, length)
        
        TotalLength = TotalLength + length
    Next i

    Dim oparams As Parameters
    Dim oparam As Parameter
    oparams = oDoc.ComponentDefinition.Parameters
    Dim exists As Boolean
    exists = False

    ''Find out if parameter exists
    For Each oparam In oparams
    If oparam.Name = "Sweeplength" Then exists = True
    Next oparam

    'Change the value if the parameter exists otherwise add the parameter
    If exists Then
        oparams.Item("Sweeplength").Value = TotalLength
    Else
        oparams.UserParameters.AddByValue( "Sweeplength", TotalLength, 11266)
    End If
    oDoc.Update
	

MessageBox.Show(Parameter("Sweeplength")& (propertyName8), "Total Sweep Length")
