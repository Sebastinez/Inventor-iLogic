Dim oPartDoc As PartDocument
oPartDoc = ThisApplication.ActiveDocument
Dim oFaces As Faces
oFaces = oPartDoc.ComponentDefinition.SurfaceBodies(1).Faces
Dim Colors As Object
Colors = CreateObject("Scripting.Dictionary")
Dim oFace As Face

For Each oFace In oFaces
	Colors(oFace.Appearance.DisplayName) = Colors(oFace.Appearance.DisplayName) + oFace.Evaluator.Area
Next

For Each Item In Colors
	MessageBox.Show("Color: " & Item & vbLf & "Area: " &Colors(Item)*0.0001 & "m^2", "Surface Area by Color")
Next
